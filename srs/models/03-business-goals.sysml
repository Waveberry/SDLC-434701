package CheqBusinessGoals {
    requirement <BG> 'Бизнес-цели Cheq' {
        requirement <BG1> 'BG-01 Меньше ручного переноса' {
            doc /* Сократить перенос покупок из фото в личный архив. */
        }
        requirement <BG2> 'BG-02 Доступный архив и цены' {
            doc /* Находить чеки и товары, сравнивать цены, делиться выбранным. */
        }
        requirement <BG3> 'BG-03 Понятные расходы и бюджет' {
            doc /* Показывать месячную сумму и остаток с учётом исторических курсов. */
        }
        requirement <BG4> 'BG-04 Сохранность и достоверность' {
            doc /* Не терять импорт и подтверждённые данные, исключать повторную запись. */
        }
        requirement <BG5> 'BG-05 Контроль данных и затрат' {
            doc /* Сохранять ручной учёт без облака, ограничивать передачу данных. */
        }
    }
}
