package CheqRequirements {
    requirement <'REQ-INT-001'> rINT_001 {
        doc /* Приложение должно предоставлять разделы «Покупки», «Товары», «Расходы» и «Настройки» с общей нижней навигацией. */
    }
    requirement <'REQ-INT-002'> rINT_002 {
        doc /* Редактор должен показывать магазин, дату, валюту, итог, позиции, карту и исходный текст, а также действия проверки и сохранения. */
    }
    requirement <'REQ-INT-003'> rINT_003 {
        doc /* Приложение должно принимать снимок с камеры и изображение через системный выбор фото; при отказе в доступе к камере должен оставаться ручной ввод. */
    }
    requirement <'REQ-INT-004'> rINT_004 {
        doc /* Приложение должно запрашивать официальные курсы НБРБ на дату покупки и учитывать масштаб котировки. */
    }
    requirement <'REQ-INT-005'> rINT_005 {
        doc /* При импорте приложение должно автоматически передавать OCR-текст, дату и валюту в сервис Groq по HTTPS напрямую либо через настроенный Worker. Фото и внутренние идентификаторы карт передаваться не должны. */
    }
    requirement <'REQ-FUNC-001'> rFUNC_001 {
        doc /* Пользователь должен иметь возможность создать покупку вручную с датой, валютой, итогом и необязательным названием магазина. */
    }
    requirement <'REQ-FUNC-002'> rFUNC_002 {
        doc /* Приложение должно читать русский и английский текст встроенными OCR-моделями на устройстве, сохранять фото и текст в очереди и передавать текст для автоматического выделения товаров через Groq. */
    }
    requirement <'REQ-FUNC-003'> rFUNC_003 {
        doc /* Пользователь должен иметь возможность исправить позиции, количество, сумму строки, цену единицы, категорию и итог до сохранения. */
    }
    requirement <'REQ-FUNC-004'> rFUNC_004 {
        doc /* Приложение должно независимо сопоставлять цену с количеством и сумму позиций с итогом; расхождение должно быть показано пользователю и подтверждено при сохранении. */
    }
    requirement <'REQ-FUNC-005'> rFUNC_005 {
        doc /* Приложение должно сохранять положительный итог без товарных строк для перевода, услуги или нечитаемого состава; платёжные реквизиты не должны становиться товарами. */
    }
    requirement <'REQ-FUNC-006'> rFUNC_006 {
        doc /* Приложение должно показывать покупки карточками или списком с датой, магазином, исходной суммой и валютой; детали должны включать состав и сохранённое фото при его наличии. */
    }
    requirement <'REQ-FUNC-007'> rFUNC_007 {
        doc /* Приложение должно искать покупки по магазину, товару и дате и сортировать их по доступным в интерфейсе признакам; настройки представления и сортировки должны сохраняться. */
    }
    requirement <'REQ-FUNC-008'> rFUNC_008 {
        doc /* Приложение должно формировать историю цен товара из сохранённых строк и позволять менять категории; цены должны оставаться в исходных валютах. */
    }
    requirement <'REQ-FUNC-009'> rFUNC_009 {
        doc /* Приложение должно поддерживать BYN, RUB, EUR, USD, KZT и PLN и сохранять исходные сумму и валюту каждой покупки при смене общей валюты. */
    }
    requirement <'REQ-FUNC-010'> rFUNC_010 {
        doc /* Расходы должны пересчитываться по курсу на дату каждой покупки; для двух иностранных валют должен применяться кросс-курс через BYN с однократным округлением результата до сотой доли. */
    }
    requirement <'REQ-FUNC-011'> rFUNC_011 {
        doc /* При отсутствии курса покупка должна сохраняться, а сводка должна явно обозначать ожидание либо неполную сумму; после восстановления сети загрузка должна повторяться. */
    }
    requirement <'REQ-FUNC-012'> rFUNC_012 {
        doc /* Пользователь должен задавать лимит для выбранных месяца и общей валюты; приложение должно показывать расход, остаток или превышение. Пустой лимит и ноль должны означать отсутствие лимита. */
    }
    requirement <'REQ-FUNC-013'> rFUNC_013 {
        doc /* При полном расчёте бюджета расход от 80% лимита должен выделяться предупреждающим цветом, а превышение 100% — цветом превышения; при запуске должно отображаться соответствующее сообщение. */
    }
    requirement <'REQ-FUNC-014'> rFUNC_014 {
        doc /* Пользователь должен добавлять, изменять и удалять карту по названию и последним четырём цифрам. Удаление карты должно сохранять покупки и снимать связь с ней. */
    }
    requirement <'REQ-FUNC-015'> rFUNC_015 {
        doc /* Приложение должно предлагать карту по подтверждённым последним четырём цифрам; неоднозначное совпадение требует ручного выбора. Явный выбор пользователя, включая «Без карты», должен иметь приоритет. */
    }
    requirement <'REQ-FUNC-016'> rFUNC_016 {
        doc /* Приложение должно показывать сумму и число покупок по картам и группе «Без карты» за выбранный месяц и открывать соответствующие покупки. */
    }
    requirement <'REQ-FUNC-017'> rFUNC_017 {
        doc /* Удержание покупки или товара должно включать множественный выбор; выбор всех должен учитывать текущий поиск. Для покупок должны быть доступны карта, экспорт и удаление, для товаров — категория и экспорт. */
    }
    requirement <'REQ-FUNC-018'> rFUNC_018 {
        doc /* Удаление выбранных покупок должно требовать подтверждения и удалять связанные строки; фото должно удаляться только после исчезновения последней ссылки. */
    }
    requirement <'REQ-FUNC-019'> rFUNC_019 {
        doc /* Действие «Поделиться» должно создавать UTF-8 TXT выбранных покупок или истории товаров и передавать файл системным средством Android. Фото, исходный OCR-текст и данные карт должны исключаться. */
    }
    requirement <'REQ-FUNC-020'> rFUNC_020 {
        doc /* Очередь импортированных чеков должна автоматически продолжать анализ при восстановлении подтверждённого подключения и при открытии приложения. Отдельного переключателя Groq в настройках нет. */
    }
    requirement <'REQ-FUNC-021'> rFUNC_021 {
        doc /* Приложение должно поддерживать светлую, тёмную и системную темы, сохранять выбранную тему и восстанавливать текущий черновик при повороте экрана. */
    }
    requirement <'REQ-PERF-001'> rPERF_001 {
        doc /* Предлагаемая цель: на согласованном Android-устройстве с 4 ГБ памяти 95% из 20 повторов открытия и поиска в архиве из 1000 чеков должны завершаться не более чем за 2 с, без сетевой загрузки. */
    }
    requirement <'REQ-PERF-002'> rPERF_002 {
        doc /* OCR, запросы курсов и Groq должны выполняться вне основного потока интерфейса с видимым состоянием обработки. */
    }
    requirement <'REQ-SEC-001'> rSEC_001 {
        doc /* База и фотографии должны находиться в приватном хранилище приложения; полная автоматическая резервная копия Android должна быть отключена. */
    }
    requirement <'REQ-SEC-002'> rSEC_002 {
        doc /* Приложение должно хранить только название карты, последние четыре цифры и локальный идентификатор; полный номер карты, срок и CVV не должны запрашиваться. */
    }
    requirement <'REQ-SEC-003'> rSEC_003 {
        doc /* Рабочие запросы к внешним сервисам должны использовать HTTPS; диагностические журналы не должны содержать API-ключи, тексты чеков и изображения. */
    }
    requirement <'REQ-REL-001'> rREL_001 {
        doc /* Запись покупки с позициями и массовые изменения должны выполняться атомарно. Сохранение покупки из очереди должно транзакционно блокировать повторную запись того же элемента. */
    }
    requirement <'REQ-REL-002'> rREL_002 {
        doc /* Недоступность Groq, неверный JSON, отсутствие курса и сетевой тайм-аут должны давать понятное сообщение с сохранением локальных данных. */
    }
    requirement <'REQ-REL-003'> rREL_003 {
        doc /* Обновление внутри пакета com.waveberry.cheq должно сохранять покупки, карты, бюджеты и курсы при миграции поддерживаемых версий базы. */
    }
    requirement <'REQ-AVAIL-001'> rAVAIL_001 {
        doc /* Ручной ввод, чтение архива, локальный OCR и статистика с сохранёнными курсами должны работать без интернета. Выделение товаров из импортированного текста требует Groq и до появления сети остаётся в очереди. */
    }
    requirement <'REQ-OBS-001'> rOBS_001 {
        doc /* Интерфейс должен различать локальный OCR, ожидание сети, обработку Groq, готовность к проверке, ошибку сервиса и ожидание курса. */
    }
    requirement <'REQ-COMP-001'> rCOMP_001 {
        doc /* Поставка исходников должна включать сведения о сторонних библиотеках, OCR-моделях, шрифте и значках и соответствующие сведения об их лицензиях. */
    }
    requirement <'REQ-INST-001'> rINST_001 {
        doc /* Приложение должно устанавливаться APK-пакетом на Android 8.0 и выше; отсутствие камеры не должно исключать ручной ввод. */
    }
    requirement <'REQ-BUILD-001'> rBUILD_001 {
        doc /* Сборка должна запускаться Gradle Wrapper с JDK 17; исходники не должны требовать обязательного Groq-ключа для локальных функций. */
    }
    requirement <'REQ-DIST-001'> rDIST_001 {
        doc /* Для демонстрации должны предоставляться APK и исходники; APK со встроенным общим ключом Groq не должен считаться готовой публичной поставкой. */
    }
    requirement <'REQ-MAINT-001'> rMAINT_001 {
        doc /* Изменение поведения должно сопровождаться обновлением README и связанных требований и проверок с сохранением идентификаторов. */
    }
    requirement <'REQ-REUSE-001'> rREUSE_001 {
        doc /* Денежные расчёты и разбор текста должны быть доступны в модуле core без обязательного Android-интерфейса. */
    }
    requirement <'REQ-PORT-001'> rPORT_001 {
        doc /* Поддерживаемая поставка должна быть нативным Android-приложением; версии для iOS, браузера и настольных ОС в текущий объём не входят. */
    }
    requirement <'REQ-COST-001'> rCOST_001 {
        doc /* Недоступность или платность облачного разбора не должна лишать пользователя ручного учёта и доступа к архиву. Ограничения и ошибки сервиса должны отображаться без потери очереди. */
    }
    requirement <'REQ-DEAD-001'> rDEAD_001 {
        doc /* Спецификация, модель, макеты и отдельная ветка должны быть подготовлены до демонстрации; конструктивные замечания преподавателя должны обрабатываться до конца текущего занятия. */
    }
    requirement <'REQ-POC-001'> rPOC_001 {
        doc /* Демонстрация должна охватывать ввод чека, исправление, сохранение, поиск и появление расхода в бюджете, включая отказ сети. */
    }
    requirement <'REQ-CM-001'> rCM_001 {
        doc /* Требования должны храниться в отдельной ветке учебного репозитория; реальная обратная связь напарника и преподавателя должна обсуждаться в pull request с решениями по замечаниям. */
    }
    requirement <'REQ-ML-001'> rML_001 {
        doc /* Локальный OCR должен использовать встроенные ML Kit Latin и Tesseract rus+eng. Выделение товаров из текста выполняется автоматически моделью openai/gpt-oss-20b через Groq со структурированным JSON-ответом; локальный парсер товаров не служит резервным автоматическим разбором. */
    }
    requirement <'REQ-ML-002'> rML_002 {
        doc /* Результат OCR и языковой модели должен оставаться предложением для пользователя; система не должна подтверждать покупку, выполнять платежи или изменять сторонние счета самостоятельно. */
    }
    requirement <'REQ-ML-003'> rML_003 {
        doc /* Отказ одного OCR-движка должен оставлять результат второго; замена облачной модели или OCR-компонента должна требовать повторной проверки корпуса текстов и арифметики. */
    }
}
